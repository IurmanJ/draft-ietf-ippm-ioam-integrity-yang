module iana-ioam-integrity-protection-methods {
  yang-version 1.1;
  namespace "urn:ietf:params:xml:ns:yang:iana-ioam-integrity-protection-methods";
  prefix iana-ioam-ipm;

  organization
    "Internet Assigned Numbers Authority (IANA)";

  contact
    "Internet Assigned Numbers Authority

     ICANN
     12025 Waterfront Drive, Suite 300
     Los Angeles, CA 90094

     Tel: +1 310 301 5800

     <mailto:iana@iana.org>";

  description
    "This YANG module is maintained by IANA and reflects
     the 'IOAM Integrity Protection Methods' registry.

     Copyright (c) 2026 IETF Trust and the persons
     identified as authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     The initial version of this YANG module is part of RFC XXXX;
     see the RFC itself for full legal notices.

  // RFC Ed.: replace the IANA_FOO_URL and remove this note

     The latest version of this YANG module is available at
     <IANA_FOO_URL>.";

  reference
    "IOAM Integrity Protection Methods
     (https://www.iana.org/assignments/ioam/ioam.xhtml)";

  revision 2026-05-08 {
    description
      "Initial version.";
    reference
      "URL of the published initial version of the module

  // RFC Ed.: replace above with the URL of the module
  //          and remove this note

       RFC XXXX: A YANG Data Model for In Situ Operations,
                 Administration, and Maintenance (IOAM)
                 Integrity-Protected Options";
  }

  /*
   * Type definitions
   */

  typedef method-id {
    type enumeration {
      enum method-0 {
        value 0;
        description
          "IPM 0: AES-GMAC, 16-octet (full) Authentication Tag,
                  12-octet Initialization Vector.";
        reference
          "RFC YYYY: Integrity Protection of In Situ Operations,
                     Administration, and Maintenance (IOAM)
                     Data Fields, Section 5";
      }
    }
    description
      "Identifier for an IOAM Integrity Protection Method,
       matching the 'IOAM Integrity Protection Methods'
       IANA registry.";
    reference
      "https://www.iana.org/assignments/ioam/ioam.xhtml";
  }
}
