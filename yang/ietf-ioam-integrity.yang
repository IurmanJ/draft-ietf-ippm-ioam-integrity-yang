module ietf-ioam-integrity {
  yang-version 1.1;
  namespace "urn:ietf:params:xml:ns:yang:ietf-ioam-integrity";
  prefix ioam-int;

  import ietf-ioam {
    prefix ioam;
    reference
      "RFC 9617: A YANG Data Model for In Situ Operations,
                 Administration, and Maintenance (IOAM)";
  }

  import iana-ioam-integrity-protection-methods {
    prefix iana-ioam-ipm;
    reference
      "RFC XXXX: A YANG Data Model for In Situ Operations,
                 Administration, and Maintenance (IOAM)
                 Integrity-Protected Options";
  }

  organization
    "IETF IPPM (IP Performance Measurement) Working Group";

  contact
    "WG Web:   <https://datatracker.ietf.org/wg/ippm>
     WG List:  IPPM <mailto:ippm@ietf.org>

     Editor:   Tianran Zhou
               <mailto:zhoutianran@huawei.com>
     Editor:   Justin Iurman
               <mailto:justin.iurman@uliege.be>";

  description
    "This YANG module specifies a vendor-independent data model for
     In Situ Operations, Administration, and Maintenance (IOAM)
     Integrity-Protected Options.

     Copyright (c) 2026 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see the
     RFC itself for full legal notices.

     Operational Considerations:

      - This model does not treat as mutually exclusive an IOAM
        Option and its integrity protected equivalent (i.e., an IOAM
        Integrity-Protected Option). For example, an implementation
        may support the simultaneous configuration of an
        IOAM-Namespace with the Pre-allocated Trace Option and
        another IOAM-Namespace with the Integrity-Protected
        Pre-allocated Trace Option. Therefore, the model does not
        impose constraints that would prevent such use cases.";

  revision 2026-05-08 {
    description
      "Initial version.";
    reference
      "RFC XXXX: A YANG Data Model for In Situ Operations,
                 Administration, and Maintenance (IOAM)
                 Integrity-Protected Options";
  }

  /*
   * FEATURES
   */

  feature int-incremental-trace {
    description
      "This feature indicates that the Integrity-Protected
       Incremental Trace-Option is supported.";
    reference
      "RFC YYYY: Integrity Protection of In Situ Operations,
                 Administration, and Maintenance (IOAM)
                 Data Fields, Section 4.1";
  }

  feature int-preallocated-trace {
    description
      "This feature indicates that the Integrity-Protected
       Pre-allocated Trace-Option is supported.";
    reference
      "RFC YYYY: Integrity Protection of In Situ Operations,
                 Administration, and Maintenance (IOAM)
                 Data Fields, Section 4.1";
  }

  feature int-proof-of-transit {
    description
      "This feature indicates that the Integrity-Protected Proof of
       Transit Option is supported.";
    reference
      "RFC YYYY: Integrity Protection of In Situ Operations,
                 Administration, and Maintenance (IOAM)
                 Data Fields, Section 4.2";
  }

  feature int-edge-to-edge {
    description
      "This feature indicates that the Integrity-Protected
       Edge-to-Edge Option is supported.";
    reference
      "RFC YYYY: Integrity Protection of In Situ Operations,
                 Administration, and Maintenance (IOAM)
                 Data Fields, Section 4.3";
  }

  /*
   * GROUP DEFINITIONS
   */

  grouping int-method-grouping {
    description
      "A grouping for Integrity Protection Methods.";
    leaf int-method {
      when "derived-from-or-self(../node-action,
            'ioam:action-encapsulate')";
      type iana-ioam-ipm:method-id;
      mandatory true;
      description
        "This object indicates the Integrity Protection Method for
         this profile. 'int-method' is only defined at the
         encapsulating node.";
    }
  }

  /*
   * DATA NODES
   */

  augment "/ioam:ioam/ioam:profiles/ioam:profile" {
    description
      "This augmentation adds 4 profiles for the Integrity-Protected
       Options.";
    container int-incremental-tracing-profile {
      if-feature "int-incremental-trace";
      presence "Enables the Integrity-Protected
                Incremental Trace-Option.";
      description
        "This container describes the profile for the
         Integrity-Protected Incremental Trace-Option.";
      uses ioam:ioam-incremental-tracing-profile;
      uses int-method-grouping;
    }
    container int-preallocated-tracing-profile {
      if-feature "int-preallocated-trace";
      presence "Enables the Integrity-Protected
                Pre-allocated Trace-Option.";
      description
        "This container describes the profile for the
         Integrity-Protected Pre-allocated Trace-Option.";
      uses ioam:ioam-preallocated-tracing-profile;
      uses int-method-grouping;
    }
    container int-pot-profile {
      if-feature "int-proof-of-transit";
      presence "Enables the Integrity-Protected
                Proof of Transit Option.";
      description
        "This container describes the profile for the
         Integrity-Protected Proof of Transit Option.";
      leaf use-namespace {
        type ioam:ioam-namespace;
        default "ioam:default-namespace";
        description
          "This object indicates the namespace used for the
           POT types.";
      }
      leaf pot-type {
        type ioam:ioam-pot-type;
        description
          "The type of a particular POT variant that specifies
           the POT data that is included.";
      }
      leaf node-action {
        type ioam:ioam-node-action;
        default "ioam:action-transit";
        description
          "This object indicates the action the node needs to
           take, e.g., encapsulation.";
      }
      uses int-method-grouping;
    }
    container int-e2e-profile {
      if-feature "int-edge-to-edge";
      presence "Enables the Integrity-Protected
                Edge-to-Edge Option.";
      description
        "This container describes the profile for the
         Integrity-Protected Edge-to-Edge Option.";
      uses ioam:ioam-e2e-profile;
      uses int-method-grouping;
    }
  }
}
